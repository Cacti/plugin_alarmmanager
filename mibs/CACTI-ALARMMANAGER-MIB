-- *****************************************************************
-- CACTI-ALARMMANAGER-MIB: alarm notifications sent by the
-- Cacti Alarm Manager plugin.
--
-- Copyright (c) 2004-2026 by The Cacti Group
-- All rights reserved.
--
-- *****************************************************************

CACTI-ALARMMANAGER-MIB DEFINITIONS ::= BEGIN

IMPORTS
    OBJECT-TYPE,
    MODULE-IDENTITY,
    NOTIFICATION-TYPE,
    Unsigned32
        FROM SNMPv2-SMI

    OBJECT-GROUP,
    NOTIFICATION-GROUP,
    MODULE-COMPLIANCE
        FROM SNMPv2-CONF

    DisplayString
        FROM SNMPv2-TC

    cacti
        FROM CACTI-MIB
;

cactiAlarmManager MODULE-IDENTITY
    LAST-UPDATED    "202610260000Z"
    ORGANIZATION    "The Cacti Group"
    CONTACT-INFO
            "The Cacti Group

            E-mail: developers@cacti.net"
    DESCRIPTION
        "Notifications forwarded by the Cacti Alarm Manager plugin.
        amAlarmRaise reports a raised, updated, reminder or
        occurrence transition; amAlarmClear reports recovery.
        Both carry amAlarmKey so a receiver can pair a raise with
        its clear. Varbinds are configurable per destination, so
        a notification may carry any subset of the amObjects."
    REVISION        "202610260000Z"
    DESCRIPTION
        "Initial version."
    ::= { cacti 6 }

amNotifications OBJECT IDENTIFIER ::= { cactiAlarmManager 0 }
amObjects       OBJECT IDENTIFIER ::= { cactiAlarmManager 1 }
amConformance   OBJECT IDENTIFIER ::= { cactiAlarmManager 2 }

amAlarmKey OBJECT-TYPE
    SYNTAX      DisplayString (SIZE (0..255))
    MAX-ACCESS  accessible-for-notify
    STATUS      current
    DESCRIPTION
        "Stable alarm identity shared by raise and clear notifications."
    ::= { amObjects 1 }

amEpisodeId OBJECT-TYPE
    SYNTAX      DisplayString (SIZE (0..255))
    MAX-ACCESS  accessible-for-notify
    STATUS      current
    DESCRIPTION
        "Identity of one alarm episode, from raise until recovery."
    ::= { amObjects 2 }

amEventId OBJECT-TYPE
    SYNTAX      DisplayString (SIZE (0..255))
    MAX-ACCESS  accessible-for-notify
    STATUS      current
    DESCRIPTION
        "Unique identity of the event that caused this notification."
    ::= { amObjects 3 }

amTransition OBJECT-TYPE
    SYNTAX      INTEGER {
                    raised(1),
                    updated(2),
                    reminder(3),
                    recovered(4),
                    occurrence(5)
                }
    MAX-ACCESS  accessible-for-notify
    STATUS      current
    DESCRIPTION
        "Alarm lifecycle transition."
    ::= { amObjects 4 }

amSeverity OBJECT-TYPE
    SYNTAX      INTEGER {
                    critical(1),
                    major(2),
                    minor(3),
                    warning(4),
                    info(5),
                    clear(6)
                }
    MAX-ACCESS  accessible-for-notify
    STATUS      current
    DESCRIPTION
        "Alarm severity."
    ::= { amObjects 5 }

amSource OBJECT-TYPE
    SYNTAX      DisplayString (SIZE (0..255))
    MAX-ACCESS  accessible-for-notify
    STATUS      current
    DESCRIPTION
        "Alarm source, such as thold or a device status producer."
    ::= { amObjects 6 }

amDeviceHostname OBJECT-TYPE
    SYNTAX      DisplayString (SIZE (0..255))
    MAX-ACCESS  accessible-for-notify
    STATUS      current
    DESCRIPTION
        "Hostname of the Cacti device."
    ::= { amObjects 7 }

amDeviceDescription OBJECT-TYPE
    SYNTAX      DisplayString (SIZE (0..255))
    MAX-ACCESS  accessible-for-notify
    STATUS      current
    DESCRIPTION
        "Description of the Cacti device."
    ::= { amObjects 8 }

amDeviceId OBJECT-TYPE
    SYNTAX      Unsigned32
    MAX-ACCESS  accessible-for-notify
    STATUS      current
    DESCRIPTION
        "Cacti device identifier."
    ::= { amObjects 9 }

amSummary OBJECT-TYPE
    SYNTAX      OCTET STRING (SIZE (0..1024))
    MAX-ACCESS  accessible-for-notify
    STATUS      current
    DESCRIPTION
        "One-line alarm summary, UTF-8 encoded."
    ::= { amObjects 10 }

amDetails OBJECT-TYPE
    SYNTAX      OCTET STRING (SIZE (0..1024))
    MAX-ACCESS  accessible-for-notify
    STATUS      current
    DESCRIPTION
        "Alarm details, UTF-8 encoded and truncated to 1024 octets."
    ::= { amObjects 11 }

amOccurredAt OBJECT-TYPE
    SYNTAX      DisplayString (SIZE (0..64))
    MAX-ACCESS  accessible-for-notify
    STATUS      current
    DESCRIPTION
        "UTC time of the event in ISO 8601 format."
    ::= { amObjects 12 }

amRuleName OBJECT-TYPE
    SYNTAX      DisplayString (SIZE (0..255))
    MAX-ACCESS  accessible-for-notify
    STATUS      current
    DESCRIPTION
        "Name of the source rule, such as a threshold, when known."
    ::= { amObjects 13 }

amMetric OBJECT-TYPE
    SYNTAX      DisplayString (SIZE (0..255))
    MAX-ACCESS  accessible-for-notify
    STATUS      current
    DESCRIPTION
        "Metric that triggered the alarm, when known."
    ::= { amObjects 14 }

amMetricValue OBJECT-TYPE
    SYNTAX      DisplayString (SIZE (0..255))
    MAX-ACCESS  accessible-for-notify
    STATUS      current
    DESCRIPTION
        "Metric value at the time of the event, when known."
    ::= { amObjects 15 }

amThreshold OBJECT-TYPE
    SYNTAX      DisplayString (SIZE (0..255))
    MAX-ACCESS  accessible-for-notify
    STATUS      current
    DESCRIPTION
        "Threshold that the metric crossed, when known."
    ::= { amObjects 16 }

amAlarmRaise NOTIFICATION-TYPE
    OBJECTS     {
                    amAlarmKey,
                    amEpisodeId,
                    amEventId,
                    amTransition,
                    amSeverity,
                    amSource,
                    amDeviceHostname,
                    amDeviceDescription,
                    amDeviceId,
                    amSummary,
                    amDetails,
                    amOccurredAt,
                    amRuleName,
                    amMetric,
                    amMetricValue,
                    amThreshold
                }
    STATUS      current
    DESCRIPTION
        "An alarm was raised, updated, re-notified or occurred."
    ::= { amNotifications 1 }

amAlarmClear NOTIFICATION-TYPE
    OBJECTS     {
                    amAlarmKey,
                    amEpisodeId,
                    amEventId,
                    amTransition,
                    amSeverity,
                    amSource,
                    amDeviceHostname,
                    amDeviceDescription,
                    amDeviceId,
                    amSummary,
                    amDetails,
                    amOccurredAt,
                    amRuleName,
                    amMetric,
                    amMetricValue,
                    amThreshold
                }
    STATUS      current
    DESCRIPTION
        "An alarm recovered. amAlarmKey matches the raise."
    ::= { amNotifications 2 }

amCompliances OBJECT IDENTIFIER ::= { amConformance 1 }
amGroups      OBJECT IDENTIFIER ::= { amConformance 2 }

amCompliance MODULE-COMPLIANCE
    STATUS      current
    DESCRIPTION
        "Compliance statement for Alarm Manager notification receivers."
    MODULE
        MANDATORY-GROUPS { amObjectGroup, amNotificationGroup }
    ::= { amCompliances 1 }

amObjectGroup OBJECT-GROUP
    OBJECTS     {
                    amAlarmKey,
                    amEpisodeId,
                    amEventId,
                    amTransition,
                    amSeverity,
                    amSource,
                    amDeviceHostname,
                    amDeviceDescription,
                    amDeviceId,
                    amSummary,
                    amDetails,
                    amOccurredAt,
                    amRuleName,
                    amMetric,
                    amMetricValue,
                    amThreshold
                }
    STATUS      current
    DESCRIPTION
        "Objects carried by Alarm Manager notifications."
    ::= { amGroups 1 }

amNotificationGroup NOTIFICATION-GROUP
    NOTIFICATIONS { amAlarmRaise, amAlarmClear }
    STATUS      current
    DESCRIPTION
        "Alarm Manager notifications."
    ::= { amGroups 2 }

END
